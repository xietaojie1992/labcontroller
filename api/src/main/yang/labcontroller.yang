module labcontroller {
    yang-version 1.1;
    namespace "urn:opendaylight:params:xml:ns:yang:labcontroller";
    prefix "labcontroller";

    revision "2019-08-22" {
        description "Initial revision of labcontroller model";
    }
}
