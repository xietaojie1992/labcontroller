module labcontroller-impl {
    yang-version 1;
    namespace "urn:opendaylight:params:xml:ns:yang:labcontroller:impl";
    prefix "labcontroller-impl";

    import config { prefix config; revision-date 2013-04-05; }
    import opendaylight-md-sal-binding { prefix md-sal-binding; revision-date 2013-10-28;}
    import rpc-context { prefix rpcx; revision-date 2013-06-17; }
    import openflowplugin-extension-registry { prefix ofp-ext-reg; revision-date 2015-04-25; }
    import openflow-switch-connection-provider { prefix openflow-switch-connection-provider; revision-date 2014-03-28; }
    import openflowjava-nx-api-config { prefix openflowjava-nx-api-config; revision-date 2014-07-11; }

    description
        "Service definition for labcontroller project";

    revision "2014-12-10" {
        description
            "Initial revision";
    }

    identity labcontroller {
        base config:module-type;
        config:java-name-prefix Labcontroller;
    }

    augment "/config:modules/config:module/config:configuration" {
        case labcontroller {
            when "/config:modules/config:module/config:type = 'labcontroller'";
            container broker {
                uses config:service-ref {
                    refine type {
                        mandatory true;
                        config:required-identity md-sal-binding:binding-broker-osgi-registry;
                    }
                }
            }


            container nicira-extension-codec-registrator {
                uses config:service-ref {
                    refine type {
                        mandatory true;
                        config:required-identity openflowjava-nx-api-config:nicira-extension-codec-registrator;
                    }
                }
            }

            container data-broker {
                uses config:service-ref {
                    refine type {
                        mandatory false;
                        config:required-identity md-sal-binding:binding-async-data-broker;
                    }
                }
            }

            container rpc-registry {
                uses config:service-ref {
                    refine type {
                        mandatory true;
                        config:required-identity md-sal-binding:binding-rpc-registry;
                    }
                }
            }

            container notification-service {
                uses config:service-ref {
                    refine type {
                        mandatory true;
                        config:required-identity md-sal-binding:binding-notification-service;
                    }
                }
            }

            container openflow-switch-connection-provider {
                uses config:service-ref {
                    refine type {
                        mandatory true;
                        config:required-identity openflow-switch-connection-provider:openflow-switch-connection-provider;
                    }
                }
            }

            container openflow-plugin-extension-registry {
                uses config:service-ref {
                    refine type {
                        mandatory true;
                        config:required-identity ofp-ext-reg:openflow-extension-registry-provider;
                    }
                }
            }
        }
    }
}
